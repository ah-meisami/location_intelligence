FME workspace esrishape2geojson_man4.fmw

Parameters:
- SourceDataset_ESRISHAPE = C:\Users\Ah_Meisami\Downloads\Compressed\Tehran-GIS-22-Gane-Jodagane-FULL-VIP_575766_3010\tahran_GIS (4)\tahran_GIS (4)\man4.shp   # Source Esri Shapefile(s)
- DestDataset_GEOJSON = C:\Users\Ah_Meisami\Desktop\call wms from leaflet\man4.json   # Destination GeoJSON File

Readers:
- ESRISHAPE_1: ESRISHAPE from $(SourceDataset_ESRISHAPE)

Writers:
- GEOJSON_1: GEOJSON to $(DestDataset_GEOJSON)

man4 (reader ESRISHAPE_1)
    attributes: AREA double, PERIMETER double, LINKS_QTY number(11,0), NEW_LU number(16,0), ACRES double
    -> man4 (writer GEOJSON_1)
man4 (writer GEOJSON_1)
    attributes: AREA float, PERIMETER float, LINKS_QTY int, NEW_LU int, ACRES float
