FME workspace xlsxr2geojson.13970217.31_38.fmw

Parameters:
- SourceDataset_XLSXR_9 = C:\Users\Ah_Meisami\Desktop\call wms from leaflet\data\excel\1-6.xlsx   # Source Microsoft Excel File(s)
- SourceDataset_XLSXR = C:\Users\Ah_Meisami\Desktop\call wms from leaflet\data\excel\31-38.xlsx   # Source Microsoft Excel File(s)
- SourceDataset_XLSXR_11 = C:\Users\Ah_Meisami\Desktop\call wms from leaflet\data\excel\31-38.xlsx   # Source Microsoft Excel File(s)
- SourceDataset_XLSXR_13 = C:\Users\Ah_Meisami\Desktop\call wms from leaflet\data\excel\31-38.xlsx   # Source Microsoft Excel File(s)
- SourceDataset_XLSXR_10 = C:\Users\Ah_Meisami\Desktop\call wms from leaflet\data\excel\31-38.xlsx   # Source Microsoft Excel File(s)
- SourceDataset_XLSXR_12 = C:\Users\Ah_Meisami\Desktop\call wms from leaflet\data\excel\31-38.xlsx   # Source Microsoft Excel File(s)
- DestDataset_GEOJSON = C:\Users\Ah_Meisami\Desktop\call wms from leaflet\data\geojson\post.json   # Destination GeoJSON File
- DestDataset_GEOJSON_9 = C:\Users\Ah_Meisami\Desktop\call wms from leaflet\data\geojson\development.json   # Destination GeoJSON File
- DestDataset_GEOJSON_7 = C:\Users\Ah_Meisami\Desktop\call wms from leaflet\data\geojson\askariye.json   # Destination GeoJSON File
- DestDataset_GEOJSON_11 = C:\Users\Ah_Meisami\Desktop\call wms from leaflet\data\geojson\kosar.json   # Destination GeoJSON File
- DestDataset_GEOJSON_8 = C:\Users\Ah_Meisami\Desktop\call wms from leaflet\data\geojson\noor.json   # Destination GeoJSON File
- DestDataset_GEOJSON_10 = C:\Users\Ah_Meisami\Desktop\call wms from leaflet\data\geojson\kosar.json   # Destination GeoJSON File

Readers:
- XLSXR_1: XLSXR from $(SourceDataset_XLSXR_9) in LL84
- XLSXR_2: XLSXR from $(SourceDataset_XLSXR) in LL84
- XLSXR_3: XLSXR from $(SourceDataset_XLSXR_11) in LL84
- XLSXR_5: XLSXR from $(SourceDataset_XLSXR_13) in LL84
- XLSXR_6: XLSXR from $(SourceDataset_XLSXR_10) in LL84
- XLSXR_7: XLSXR from $(SourceDataset_XLSXR_12) in LL84

Writers:
- GEOJSON_1: GEOJSON to $(DestDataset_GEOJSON)
- GEOJSON_2: GEOJSON to $(DestDataset_GEOJSON_9)
- GEOJSON_3: GEOJSON to $(DestDataset_GEOJSON_7)
- GEOJSON_4: GEOJSON to $(DestDataset_GEOJSON_11)
- GEOJSON_5: GEOJSON to $(DestDataset_GEOJSON_8)
- GEOJSON_6: GEOJSON to $(DestDataset_GEOJSON_10)

post (reader XLSXR_2)
    attributes: branchId number(5,0), branchcode number(8,0), branchname char(21), address char(80), telephone char(19), fax number(11,0), zipcode z_coordinate, atm char(4), currencyService char(4), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(30), cityname char(12), provincename char(12), bankname char(20),
      logo char(13), provinceid number(3,0), telcode number(3,0), citytelcode string
    -> post (writer GEOJSON_1)
post (writer GEOJSON_1)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
development (reader XLSXR_3)
    attributes: branchId number(5,0), branchcode number(5,0), branchname char(15), address char(82), telephone char(37), fax char(13), zipcode z_coordinate, atm char(4), currencyService char(4), safeDeposit char(3), queueSystem char(4), issuanceCard char(3), parking char(3), eveningTime char(3), swift char(4), pinpad char(3), sms char(3), telebank char(3), webKiosk char(3), pls char(3), latitude y_coordinate, longitude x_coordinate, bankid number(5,0), cityId number(4,0), pos char(3), shetab char(4), workhours char(33), cityname char(9), provincename char(12), bankname char(20),
      logo char(20), provinceid number(3,0), telcode number(3,0), citytelcode string
    -> development (writer GEOJSON_2)
development (writer GEOJSON_2)
    attributes: branchId int, branchcode int, branchname string, address string, telephone string, fax string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
askariye (reader XLSXR_5)
    attributes: branchId number(5,0), branchcode number(4,0), branchname char(23), address char(96), telephone char(36), fax number(9,0), zipcode z_coordinate, atm char(4), currencyService char(3), safeDeposit char(3), queueSystem char(4), issuanceCard char(4), parking char(3), eveningTime char(3), swift char(3), pinpad char(3), sms char(4), telebank char(4), webKiosk char(3), pls char(3), latitude y_coordinate, longitude x_coordinate, bankid number(5,0), cityId number(4,0), pos char(3), shetab char(4), workhours char(30), cityname char(17), provincename char(12), bankname char(21),
      logo char(17), provinceid number(3,0), telcode number(3,0), citytelcode string
    -> askariye (writer GEOJSON_3)
askariye (writer GEOJSON_3)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
kosar (reader XLSXR_6)
    attributes: branchId number(5,0), branchcode number(8,0), branchname char(19), address char(91), telephone char(20), fax number(9,0), zipcode z_coordinate, atm char(4), currencyService char(3), safeDeposit char(3), queueSystem char(4), issuanceCard char(4), parking char(3), eveningTime char(4), swift char(3), pinpad char(3), sms char(4), telebank char(4), webKiosk char(3), pls char(3), latitude y_coordinate, longitude x_coordinate, bankid number(5,0), cityId number(4,0), pos char(3), shetab char(4), workhours char(30), cityname char(11), provincename char(12), bankname char(19),
      logo char(14), provinceid number(3,0), telcode number(3,0), citytelcode string
    -> kosar (writer GEOJSON_4)
kosar (writer GEOJSON_4)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
noor (reader XLSXR_7)
    attributes: branchId number(5,0), branchcode number(8,0), branchname char(24), address char(89), telephone char(27), fax number(9,0), zipcode string, atm char(3), currencyService char(3), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(30), cityname char(11), provincename char(9), bankname char(4),
      logo char(13), provinceid number(3,0), telcode number(3,0), citytelcode string
    -> noor (writer GEOJSON_5)
noor (writer GEOJSON_5)
    attributes: branchId int, branchcode int, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
kosar (reader XLSXR_7)
    attributes: branchId number(5,0), branchcode number(8,0), branchname char(19), address char(91), telephone char(20), fax number(9,0), zipcode z_coordinate, atm char(4), currencyService char(3), safeDeposit char(3), queueSystem char(4), issuanceCard char(4), parking char(3), eveningTime char(4), swift char(3), pinpad char(3), sms char(4), telebank char(4), webKiosk char(3), pls char(3), latitude y_coordinate, longitude x_coordinate, bankid number(5,0), cityId number(4,0), pos char(3), shetab char(4), workhours char(30), cityname char(11), provincename char(12), bankname char(19),
      logo char(14), provinceid number(3,0), telcode number(3,0), citytelcode string
    -> kosar (writer GEOJSON_6)
kosar (writer GEOJSON_6)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
