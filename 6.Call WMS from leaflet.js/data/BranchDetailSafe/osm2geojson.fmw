FME workspace osm2geojson.fmw

Parameters:
- SourceDataset_OSM = C:\Users\Ah_Meisami\Desktop\data_iran_lavizan\1.data.osm\map.osm   # Source OpenStreetMap File(s)
- DestDataset_GEOJSON = C:\Users\Ah_Meisami\Desktop\data_iran_lavizan\1.data.osm\1.json   # Destination GeoJSON File

Readers:
- OSM_1: OSM from $(SourceDataset_OSM) in LL84

Writers:
- GEOJSON_1: GEOJSON to $(DestDataset_GEOJSON)

building (reader OSM_1)
    attributes: created_by xml_buffer, area xml_buffer, tag{}.k xml_buffer, tag{}.v xml_buffer, nd{}.ref xml_buffer, member{}.type xml_buffer, member{}.ref xml_buffer, member{}.role xml_buffer, osm_feature_type xml_buffer, osm_theme xml_buffer, source xml_buffer, military xml_buffer, denomination xml_buffer, ref:ruian:building xml_buffer, building:ruian:type xml_buffer, construction xml_buffer, fixme xml_buffer, tourism xml_buffer, ref:bag xml_buffer, source:date xml_buffer, religion xml_buffer, amenity xml_buffer, start_date xml_buffer, layer xml_buffer, building:use:pl xml_buffer, addr:housenumber xml_buffer, addr:city xml_buffer, addr:postcode xml_buffer, power xml_buffer, substation xml_buffer,
      building:usage:pl xml_buffer, building:levels xml_buffer, name xml_buffer, addr:street xml_buffer, height xml_buffer, building xml_buffer
    -> building (writer GEOJSON_1)
building (writer GEOJSON_1)
    attributes: id string, timestamp string, user string, visible string, created_by string, area string, uid string, version string, changeset string, tag{}.k string, tag{}.v string, nd{}.ref string, member{}.type string, member{}.ref string, member{}.role string, osm_feature_type string, osm_theme string, source string, military string, denomination string, ref:ruian:building string, building:ruian:type string, construction string, fixme string, tourism string, ref:bag string, source:date string, religion string, amenity string, start_date string,
      layer string, building:use:pl string, addr:housenumber string, addr:city string, addr:postcode string, power string, substation string, building:usage:pl string, building:levels string, name string, addr:street string, height string, building string
