FME workspace esrishape2geojson_stadium-shape.fmw

Parameters:
- SourceDataset_ESRISHAPE = C:\Users\Ah_Meisami\Downloads\Compressed\TEHRAN-SHP-FILES-Full-VIP_1756444_5162\TEHRAN\sport\stadium-shape.shp   # Source Esri Shapefile(s)
- DestDataset_GEOJSON = C:\Users\Ah_Meisami\Desktop\call wms from leaflet\stadium-shape.json   # Destination GeoJSON File

Readers:
- ESRISHAPE_1: ESRISHAPE from $(SourceDataset_ESRISHAPE)

Writers:
- GEOJSON_1: GEOJSON to $(DestDataset_GEOJSON)

stadium-shape (reader ESRISHAPE_1)
    attributes: ENTITY char(14), MSLINK_DMR number(11,0), FNAME char(32), MAPID short, NAME char(34), KIND char(9), CAPACITY long, OPERATION_ char(17), RECNO long
    -> stadium-shape (writer GEOJSON_1)
stadium-shape (writer GEOJSON_1)
    attributes: ENTITY string, MSLINK_DMR int, FNAME string, MAPID int, NAME string, KIND string, CAPACITY int, OPERATION_ string, RECNO int
