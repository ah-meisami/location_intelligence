FME workspace esrishape2geojson_IRN_adm2.fmw

Parameters:
- SourceDataset_ESRISHAPE = C:\Users\Ah_Meisami\Downloads\Compressed\IRN_adm\IRN_adm2.shp   # Source Esri Shapefile(s)
- DestDataset_GEOJSON = C:\Users\Ah_Meisami\Desktop\call wms from leaflet\IRN_adm2.json   # Destination GeoJSON File

Readers:
- ESRISHAPE_1: ESRISHAPE from $(SourceDataset_ESRISHAPE)

Writers:
- GEOJSON_1: GEOJSON to $(DestDataset_GEOJSON)

IRN_adm2 (reader ESRISHAPE_1)
    attributes: ID_0 long, ISO char(3), NAME_0 char(75), ID_1 long, NAME_1 char(75), ID_2 long, NAME_2 char(75), TYPE_2 char(50), ENGTYPE_2 char(50), NL_NAME_2 char(75), VARNAME_2 char(150)
    -> IRN_adm2 (writer GEOJSON_1)
IRN_adm2 (writer GEOJSON_1)
    attributes: NAME0 string, NAME1 string, NAME2 string
