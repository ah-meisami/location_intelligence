FME workspace xlsxr2geojson.13970217.25_30.fmw

Parameters:
- SourceDataset_XLSXR_9 = C:\Users\Ah_Meisami\Desktop\call wms from leaflet\data\excel\1-6.xlsx   # Source Microsoft Excel File(s)
- SourceDataset_XLSXR = C:\Users\Ah_Meisami\Desktop\call wms from leaflet\data\excel\25-30.xlsx   # Source Microsoft Excel File(s)
- SourceDataset_XLSXR_11 = C:\Users\Ah_Meisami\Desktop\call wms from leaflet\data\excel\25-30.xlsx   # Source Microsoft Excel File(s)
- SourceDataset_XLSXR_8 = C:\Users\Ah_Meisami\Desktop\call wms from leaflet\data\excel\25-30.xlsx   # Source Microsoft Excel File(s)
- SourceDataset_XLSXR_7 = C:\Users\Ah_Meisami\Desktop\call wms from leaflet\data\excel\25-30.xlsx   # Source Microsoft Excel File(s)
- SourceDataset_XLSXR_10 = C:\Users\Ah_Meisami\Desktop\call wms from leaflet\data\excel\25-30.xlsx   # Source Microsoft Excel File(s)
- DestDataset_GEOJSON = C:\Users\Ah_Meisami\Desktop\call wms from leaflet\data\geojson\meli.json   # Destination GeoJSON File
- DestDataset_GEOJSON_9 = C:\Users\Ah_Meisami\Desktop\call wms from leaflet\data\geojson\mellat.json   # Destination GeoJSON File
- DestDataset_GEOJSON_7 = C:\Users\Ah_Meisami\Desktop\call wms from leaflet\data\geojson\maskan.json   # Destination GeoJSON File
- DestDataset_GEOJSON_6 = C:\Users\Ah_Meisami\Desktop\call wms from leaflet\data\geojson\tourism.json   # Destination GeoJSON File
- DestDataset_GEOJSON_8 = C:\Users\Ah_Meisami\Desktop\call wms from leaflet\data\geojson\agricultural.json   # Destination GeoJSON File

Readers:
- XLSXR_1: XLSXR from $(SourceDataset_XLSXR_9) in LL84
- XLSXR_2: XLSXR from $(SourceDataset_XLSXR) in LL4
- XLSXR_3: XLSXR from $(SourceDataset_XLSXR_11) in LL4
- XLSXR_4: XLSXR from $(SourceDataset_XLSXR_8) in LL4
- XLSXR_5: XLSXR from $(SourceDataset_XLSXR_7) in LL4
- XLSXR_6: XLSXR from $(SourceDataset_XLSXR_10) in LL4

Writers:
- GEOJSON_1: GEOJSON to $(DestDataset_GEOJSON)
- GEOJSON_2: GEOJSON to $(DestDataset_GEOJSON_9)
- GEOJSON_3: GEOJSON to $(DestDataset_GEOJSON_7)
- GEOJSON_4: GEOJSON to $(DestDataset_GEOJSON_6)
- GEOJSON_5: GEOJSON to $(DestDataset_GEOJSON_8)

agricultural (reader XLSXR_2)
    attributes: branchId number(5,0), branchcode char(11), branchname char(42), address char(101), telephone char(49), fax char(19), zipcode char(13), atm char(4), currencyService char(4), safeDeposit char(3), queueSystem char(4), issuanceCard char(4), parking char(3), eveningTime char(3), swift char(3), pinpad char(3), sms char(3), telebank char(3), webKiosk char(3), pls char(3), latitude y_coordinate, longitude x_coordinate, bankid number(5,0), cityId number(4,0), pos char(3), shetab char(4), workhours char(30), cityname char(14), provincename char(12), bankname char(13),
      logo char(21), provinceid number(3,0), telcode number(3,0), citytelcode string
    -> agricultural (writer GEOJSON_5)
agricultural (writer GEOJSON_5)
    attributes: branchId int, branchcode string, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
tourism (reader XLSXR_3)
    attributes: branchId number(5,0), branchcode number(5,0), branchname char(24), address char(94), telephone char(20), fax number(9,0), zipcode string, atm char(4), currencyService char(4), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(30), cityname char(6), provincename char(12), bankname char(13),
      logo char(16), provinceid number(3,0), telcode number(3,0), citytelcode string
    -> tourism (writer GEOJSON_4)
tourism (writer GEOJSON_4)
    attributes: branchId int, branchcode int, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
maskan (reader XLSXR_4)
    attributes: branchId number(5,0), branchcode number(5,0), branchname char(28), address char(90), telephone char(51), fax char(36), zipcode char(14), atm char(4), currencyService char(4), safeDeposit char(4), queueSystem char(4), issuanceCard char(4), parking char(3), eveningTime char(3), swift char(3), pinpad char(3), sms char(3), telebank char(3), webKiosk char(4), pls char(3), latitude y_coordinate, longitude x_coordinate, bankid number(5,0), cityId number(4,0), pos char(3), shetab char(4), workhours char(29), cityname char(17), provincename char(12), bankname char(10),
      logo char(15), provinceid number(3,0), telcode number(3,0), citytelcode string
    -> maskan (writer GEOJSON_3)
maskan (writer GEOJSON_3)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
mellat (reader XLSXR_5)
    attributes: branchId number(5,0), branchcode char(7), branchname char(40), address char(101), telephone char(27), fax char(18), zipcode char(13), atm char(4), currencyService char(4), safeDeposit char(3), queueSystem char(4), issuanceCard char(4), parking char(4), eveningTime char(3), swift char(3), pinpad char(3), sms char(4), telebank char(4), webKiosk char(3), pls char(3), latitude y_coordinate, longitude x_coordinate, bankid number(5,0), cityId number(4,0), pos char(4), shetab char(4), workhours char(31), cityname char(17), provincename char(15), bankname char(9),
      logo char(15), provinceid number(3,0), telcode number(3,0), citytelcode string
    -> mellat (writer GEOJSON_2)
mellat (writer GEOJSON_2)
    attributes: branchId int, branchcode string, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
meli (reader XLSXR_6)
    attributes: branchId number(5,0), branchcode char(27), branchname char(45), address char(101), telephone char(22), fax char(18), zipcode char(34), atm char(4), currencyService char(4), safeDeposit char(4), queueSystem char(4), issuanceCard char(4), parking char(4), eveningTime char(4), swift char(4), pinpad char(4), sms char(4), telebank char(4), webKiosk char(4), pls char(4), latitude y_coordinate, longitude x_coordinate, bankid number(5,0), cityId number(4,0), pos char(3), shetab char(4), workhours char(30), cityname char(17), provincename char(12), bankname char(15),
      logo char(13), provinceid number(3,0), telcode number(3,0), citytelcode string
    -> meli (writer GEOJSON_1)
meli (writer GEOJSON_1)
    attributes: branchId int, branchcode string, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
