FME workspace esrishape2geojson_tehran.fmw

Parameters:
- SourceDataset_ESRISHAPE = C:\Users\Ah_Meisami\Downloads\Compressed\tehran_manategh22\tehran.shp   # Source Esri Shapefile(s)
- DestDataset_GEOJSON = C:\Users\Ah_Meisami\Desktop\call wms from leaflet\tehran.json   # Destination GeoJSON File

Readers:
- ESRISHAPE_1: ESRISHAPE from $(SourceDataset_ESRISHAPE)

Writers:
- GEOJSON_1: GEOJSON to $(DestDataset_GEOJSON)

tehran (reader ESRISHAPE_1)
    attributes: manategh double
    -> tehran (writer GEOJSON_1)
tehran (writer GEOJSON_1)
    attributes: manategh float
