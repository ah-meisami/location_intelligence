FME workspace xlsxr2geojson.13970217.19_24.fmw

Parameters:
- SourceDataset_XLSXR_9 = C:\Users\Ah_Meisami\Desktop\call wms from leaflet\data\excel\1-6.xlsx   # Source Microsoft Excel File(s)
- SourceDataset_XLSXR = C:\Users\Ah_Meisami\Desktop\call wms from leaflet\data\excel\19-24.xlsx   # Source Microsoft Excel File(s)
- SourceDataset_XLSXR_11 = C:\Users\Ah_Meisami\Desktop\call wms from leaflet\data\excel\19-24.xlsx   # Source Microsoft Excel File(s)
- SourceDataset_XLSXR_8 = C:\Users\Ah_Meisami\Desktop\call wms from leaflet\data\excel\19-24.xlsx   # Source Microsoft Excel File(s)
- SourceDataset_XLSXR_13 = C:\Users\Ah_Meisami\Desktop\call wms from leaflet\data\excel\19-24.xlsx   # Source Microsoft Excel File(s)
- SourceDataset_XLSXR_10 = C:\Users\Ah_Meisami\Desktop\call wms from leaflet\data\excel\19-24.xlsx   # Source Microsoft Excel File(s)
- SourceDataset_XLSXR_12 = C:\Users\Ah_Meisami\Desktop\call wms from leaflet\data\excel\19-24.xlsx   # Source Microsoft Excel File(s)
- DestDataset_GEOJSON = C:\Users\Ah_Meisami\Desktop\call wms from leaflet\data\geojson\ghavamin.json   # Destination GeoJSON File
- DestDataset_GEOJSON_9 = C:\Users\Ah_Meisami\Desktop\call wms from leaflet\data\geojson\saderat_iran.json   # Destination GeoJSON File
- DestDataset_GEOJSON_7 = C:\Users\Ah_Meisami\Desktop\call wms from leaflet\data\geojson\kar_afarin.json   # Destination GeoJSON File
- DestDataset_GEOJSON_11 = C:\Users\Ah_Meisami\Desktop\call wms from leaflet\data\geojson\industry_mine.json   # Destination GeoJSON File
- DestDataset_GEOJSON_8 = C:\Users\Ah_Meisami\Desktop\call wms from leaflet\data\geojson\mehr_iran.json   # Destination GeoJSON File
- DestDataset_GEOJSON_10 = C:\Users\Ah_Meisami\Desktop\call wms from leaflet\data\geojson\resalat.json   # Destination GeoJSON File

Readers:
- XLSXR_1: XLSXR from $(SourceDataset_XLSXR_9) in LL84
- XLSXR_2: XLSXR from $(SourceDataset_XLSXR) in LL84
- XLSXR_3: XLSXR from $(SourceDataset_XLSXR_11) in LL84
- XLSXR_4: XLSXR from $(SourceDataset_XLSXR_8) in LL84
- XLSXR_5: XLSXR from $(SourceDataset_XLSXR_13) in LL84
- XLSXR_6: XLSXR from $(SourceDataset_XLSXR_10) in LL84
- XLSXR_7: XLSXR from $(SourceDataset_XLSXR_12) in LL84

Writers:
- GEOJSON_1: GEOJSON to $(DestDataset_GEOJSON)
- GEOJSON_2: GEOJSON to $(DestDataset_GEOJSON_9)
- GEOJSON_3: GEOJSON to $(DestDataset_GEOJSON_7)
- GEOJSON_4: GEOJSON to $(DestDataset_GEOJSON_11)
- GEOJSON_5: GEOJSON to $(DestDataset_GEOJSON_8)
- GEOJSON_6: GEOJSON to $(DestDataset_GEOJSON_10)

saderat_iran (reader XLSXR_2)
    attributes: branchId number(5,0), branchcode char(6), branchname char(32), address char(97), telephone char(51), fax char(18), zipcode z_coordinate, atm char(4), currencyService char(4), safeDeposit char(4), queueSystem char(4), issuanceCard char(4), parking char(3), eveningTime char(3), swift char(3), pinpad char(3), sms char(4), telebank char(4), webKiosk char(3), pls char(3), latitude y_coordinate, longitude x_coordinate, bankid number(5,0), cityId number(4,0), pos char(3), shetab char(4), workhours char(30), cityname char(17), provincename char(12), bankname char(18),
      logo char(21), provinceid number(3,0), telcode number(3,0), citytelcode string
    -> saderat_iran (writer GEOJSON_2)
saderat_iran (writer GEOJSON_2)
    attributes: branchId int, branchcode string, branchname string, address string, telephone string, fax string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
industry_mine (reader XLSXR_3)
    attributes: branchId number(5,0), branchcode number(4,0), branchname char(34), address char(93), telephone char(22), fax number(9,0), zipcode z_coordinate, atm char(4), currencyService char(3), safeDeposit char(3), queueSystem char(4), issuanceCard char(4), parking char(3), eveningTime char(3), swift char(3), pinpad char(3), sms char(4), telebank char(4), webKiosk char(3), pls char(3), latitude y_coordinate, longitude x_coordinate, bankid number(5,0), cityId number(4,0), pos char(3), shetab char(4), workhours char(30), cityname char(10), provincename char(12), bankname char(17),
      logo char(22), provinceid number(3,0), telcode number(3,0), citytelcode string
    -> industry_mine (writer GEOJSON_4)
industry_mine (writer GEOJSON_4)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
resalat (reader XLSXR_4)
    attributes: branchId number(5,0), branchcode number(5,0), branchname char(16), address char(83), telephone char(15), fax string, zipcode string, atm char(4), currencyService char(3), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(30), cityname char(17), provincename char(12), bankname char(22),
      logo char(16), provinceid number(3,0), telcode number(3,0), citytelcode string
    -> resalat (writer GEOJSON_6)
resalat (writer GEOJSON_6)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
mehr_iran (reader XLSXR_5)
    attributes: branchId number(5,0), branchcode number(5,0), branchname char(25), address char(79), telephone char(14), fax char(15), zipcode char(12), atm char(4), currencyService char(3), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(4), shetab char(4), workhours char(36), cityname char(12), provincename char(12), bankname char(26),
      logo char(18), provinceid number(3,0), telcode number(3,0), citytelcode string
    -> mehr_iran (writer GEOJSON_5)
mehr_iran (writer GEOJSON_5)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
ghavamin (reader XLSXR_6)
    attributes: branchId number(5,0), branchcode char(12), branchname char(24), address char(101), telephone char(29), fax char(13), zipcode string, atm char(4), currencyService char(3), safeDeposit char(3), queueSystem char(4), issuanceCard char(4), parking char(3), eveningTime char(3), swift char(3), pinpad char(3), sms char(3), telebank char(3), webKiosk char(3), pls char(3), latitude y_coordinate, longitude x_coordinate, bankid number(5,0), cityId number(4,0), pos char(3), shetab char(4), workhours char(30), cityname char(17), provincename char(12), bankname char(12),
      logo char(17), provinceid number(3,0), telcode number(3,0), citytelcode string
    -> ghavamin (writer GEOJSON_1)
ghavamin (writer GEOJSON_1)
    attributes: branchId int, branchcode string, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
kar_afarin (reader XLSXR_7)
    attributes: branchId number(5,0), branchcode char(13), branchname char(19), address char(92), telephone char(12), fax char(12), zipcode z_coordinate, atm char(4), currencyService char(4), safeDeposit char(4), queueSystem char(4), issuanceCard char(4), parking char(3), eveningTime char(3), swift char(3), pinpad char(3), sms char(4), telebank char(3), webKiosk char(3), pls char(3), latitude y_coordinate, longitude x_coordinate, bankid number(2,0), cityId number(4,0), pos char(4), shetab char(4), workhours char(31), cityname char(7), provincename char(12), bankname char(14),
      logo char(19), provinceid number(3,0), telcode number(3,0), citytelcode string
    -> kar_afarin (writer GEOJSON_3)
kar_afarin (writer GEOJSON_3)
    attributes: branchId int, branchcode string, branchname string, address string, telephone string, fax string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
