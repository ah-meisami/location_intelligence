FME workspace esrishape2geojson_IRN_adm1.fmw

Parameters:
- SourceDataset_ESRISHAPE = C:\Users\Ah_Meisami\Downloads\Compressed\IRN_adm\IRN_adm1.shp   # Source Esri Shapefile(s)
- DestDataset_GEOJSON = C:\Users\Ah_Meisami\Desktop\call wms from leaflet\IRN_adm1.json   # Destination GeoJSON File

Readers:
- ESRISHAPE_1: ESRISHAPE from $(SourceDataset_ESRISHAPE)

Writers:
- GEOJSON_1: GEOJSON to $(DestDataset_GEOJSON)

IRN_adm1 (reader ESRISHAPE_1)
    attributes: ID_0 long, ISO char(3), NAME_0 char(75), ID_1 long, NAME_1 char(75), TYPE_1 char(50), ENGTYPE_1 char(50), NL_NAME_1 char(50), VARNAME_1 char(150)
    -> IRN_adm1 (writer GEOJSON_1)
IRN_adm1 (writer GEOJSON_1)
    attributes: ID_0 int, ISO string, NAME_0 string, ID_1 int, NAME_1 string, TYPE_1 string, ENGTYPE_1 string, NL_NAME_1 string, VARNAME_1 string
