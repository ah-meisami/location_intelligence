FME workspace xlsxr2geojson.13970217.13_18.fmw

Parameters:
- SourceDataset_XLSXR_9 = C:\Users\Ah_Meisami\Desktop\call wms from leaflet\data\excel\1-6.xlsx   # Source Microsoft Excel File(s)
- SourceDataset_XLSXR = C:\Users\Ah_Meisami\Desktop\call wms from leaflet\data\excel\13-18.xlsx   # Source Microsoft Excel File(s)
- DestDataset_GEOJSON = C:\Users\Ah_Meisami\Desktop\call wms from leaflet\data\geojson\refah_kargaran.json   # Destination GeoJSON File
- SourceDataset_XLSXR_11 = C:\Users\Ah_Meisami\Desktop\call wms from leaflet\data\excel\13-18.xlsx   # Source Microsoft Excel File(s)
- SourceDataset_XLSXR_8 = C:\Users\Ah_Meisami\Desktop\call wms from leaflet\data\excel\13-18.xlsx   # Source Microsoft Excel File(s)
- SourceDataset_XLSXR_13 = C:\Users\Ah_Meisami\Desktop\call wms from leaflet\data\excel\13-18.xlsx   # Source Microsoft Excel File(s)
- SourceDataset_XLSXR_10 = C:\Users\Ah_Meisami\Desktop\call wms from leaflet\data\excel\13-18.xlsx   # Source Microsoft Excel File(s)
- SourceDataset_XLSXR_12 = C:\Users\Ah_Meisami\Desktop\call wms from leaflet\data\excel\13-18.xlsx   # Source Microsoft Excel File(s)
- DestDataset_GEOJSON_9 = C:\Users\Ah_Meisami\Desktop\call wms from leaflet\data\geojson\saman.json   # Destination GeoJSON File
- DestDataset_GEOJSON_7 = C:\Users\Ah_Meisami\Desktop\call wms from leaflet\data\geojson\sarmaye.json   # Destination GeoJSON File
- DestDataset_GEOJSON_11 = C:\Users\Ah_Meisami\Desktop\call wms from leaflet\data\geojson\sina.json   # Destination GeoJSON File
- DestDataset_GEOJSON_8 = C:\Users\Ah_Meisami\Desktop\call wms from leaflet\data\geojson\shahr.json   # Destination GeoJSON File
- DestDataset_GEOJSON_10 = C:\Users\Ah_Meisami\Desktop\call wms from leaflet\data\geojson\sepah.json   # Destination GeoJSON File

Readers:
- XLSXR_1: XLSXR from $(SourceDataset_XLSXR_9) in LL84
- XLSXR_2: XLSXR from $(SourceDataset_XLSXR) in LL84
- XLSXR_3: XLSXR from $(SourceDataset_XLSXR_11) in LL84
- XLSXR_4: XLSXR from $(SourceDataset_XLSXR_8) in LL84
- XLSXR_5: XLSXR from $(SourceDataset_XLSXR_13) in LL84
- XLSXR_6: XLSXR from $(SourceDataset_XLSXR_10) in LL84
- XLSXR_7: XLSXR from $(SourceDataset_XLSXR_12) in LL84

Writers:
- GEOJSON_1: GEOJSON to $(DestDataset_GEOJSON)
- GEOJSON_2: GEOJSON to $(DestDataset_GEOJSON_9)
- GEOJSON_3: GEOJSON to $(DestDataset_GEOJSON_7)
- GEOJSON_4: GEOJSON to $(DestDataset_GEOJSON_11)
- GEOJSON_5: GEOJSON to $(DestDataset_GEOJSON_8)
- GEOJSON_6: GEOJSON to $(DestDataset_GEOJSON_10)

saman (reader XLSXR_3)
    attributes: branchId number(5,0), branchcode number(5,0), branchname char(27), address char(101), telephone char(21), fax number(9,0), zipcode z_coordinate, atm char(4), currencyService char(3), safeDeposit char(3), queueSystem char(4), issuanceCard char(4), parking char(3), eveningTime char(3), swift char(3), pinpad char(3), sms char(4), telebank char(4), webKiosk char(3), pls char(3), latitude y_coordinate, longitude x_coordinate, bankid number(2,0), cityId number(4,0), pos char(3), shetab char(4), workhours char(30), cityname char(8), provincename char(12), bankname char(11),
      logo char(14), provinceid number(3,0), telcode number(3,0), citytelcode string
    -> saman (writer GEOJSON_2)
saman (writer GEOJSON_2)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
sepah (reader XLSXR_4)
    attributes: branchId number(5,0), branchcode number(5,0), branchname char(36), address char(101), telephone char(20), fax char(13), zipcode char(11), atm char(4), currencyService char(4), safeDeposit char(4), queueSystem char(4), issuanceCard char(4), parking char(3), eveningTime char(4), swift char(3), pinpad char(4), sms char(4), telebank char(4), webKiosk char(4), pls char(4), latitude y_coordinate, longitude x_coordinate, bankid number(5,0), cityId number(4,0), pos char(4), shetab char(4), workhours char(30), cityname char(17), provincename char(12), bankname char(9),
      logo char(14), provinceid number(3,0), telcode number(3,0), citytelcode string
    -> sepah (writer GEOJSON_6)
sepah (writer GEOJSON_6)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
sarmaye (reader XLSXR_5)
    attributes: branchId number(5,0), branchcode char(6), branchname char(25), address char(101), telephone char(28), fax number(9,0), zipcode string, atm char(4), currencyService char(4), safeDeposit char(3), queueSystem char(4), issuanceCard char(4), parking char(3), eveningTime char(4), swift char(3), pinpad char(4), sms char(4), telebank char(4), webKiosk char(3), pls char(3), latitude y_coordinate, longitude x_coordinate, bankid number(2,0), cityId number(4,0), pos char(3), shetab char(4), workhours char(31), cityname char(10), provincename char(12), bankname char(12),
      logo char(16), provinceid number(3,0), telcode number(3,0), citytelcode string
    -> sarmaye (writer GEOJSON_3)
sarmaye (writer GEOJSON_3)
    attributes: branchId int, branchcode string, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
sina (reader XLSXR_6)
    attributes: branchId number(5,0), branchcode number(5,0), branchname char(25), address char(100), telephone char(29), fax char(10), zipcode string, atm char(4), currencyService char(4), safeDeposit char(4), queueSystem char(4), issuanceCard char(4), parking char(3), eveningTime char(3), swift char(3), pinpad char(4), sms char(3), telebank char(4), webKiosk char(3), pls char(3), latitude y_coordinate, longitude x_coordinate, bankid number(2,0), cityId number(4,0), pos char(3), shetab char(4), workhours char(30), cityname char(17), provincename char(12), bankname char(10),
      logo char(13), provinceid number(3,0), telcode number(3,0), citytelcode string
    -> sina (writer GEOJSON_4)
sina (writer GEOJSON_4)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
refah_kargaran (reader XLSXR_2)
    attributes: branchId number(5,0), branchcode number(5,0), branchname char(37), address char(94), telephone char(18), fax number(9,0), zipcode string, atm char(4), currencyService char(4), safeDeposit char(4), queueSystem char(4), issuanceCard char(4), parking char(3), eveningTime char(4), swift char(3), pinpad char(3), sms char(3), telebank char(3), webKiosk char(4), pls char(3), latitude y_coordinate, longitude x_coordinate, bankid number(5,0), cityId number(4,0), pos char(4), shetab char(4), workhours char(30), cityname char(17), provincename char(12), bankname char(18),
      logo char(23), provinceid number(3,0), telcode number(3,0), citytelcode string
    -> refah_kargaran (writer GEOJSON_1)
refah_kargaran (writer GEOJSON_1)
    attributes: branchId int, branchcode int, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
shahr (reader XLSXR_7)
    attributes: branchId number(5,0), branchcode number(5,0), branchname char(25), address char(101), telephone char(23), fax number(9,0), zipcode z_coordinate, atm char(4), currencyService char(4), safeDeposit char(4), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(30), cityname char(10), provincename char(12), bankname char(9),
      logo char(14), provinceid number(3,0), telcode number(3,0), citytelcode string
    -> shahr (writer GEOJSON_5)
shahr (writer GEOJSON_5)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
