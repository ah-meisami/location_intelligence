FME workspace esrishape2geojson_world.fmw

Parameters:
- SourceDataset_ESRISHAPE = C:\Users\Ah_Meisami\Downloads\Compressed\TM_WORLD_BORDERS-0.3\TM_WORLD_BORDERS-0.3.shp   # Source Esri Shapefile(s)
- DestDataset_GEOJSON = C:\Users\Ah_Meisami\Desktop\call wms from leaflet\world.json   # Destination GeoJSON File

Readers:
- ESRISHAPE_1: ESRISHAPE from $(SourceDataset_ESRISHAPE)

Writers:
- GEOJSON_1: GEOJSON to $(DestDataset_GEOJSON)

TM_WORLD_BORDERS-0.3 (reader ESRISHAPE_1)
    attributes: FIPS char(2), ISO2 char(2), ISO3 char(3), UN short, NAME char(50), AREA long, POP2005 long, REGION short, SUBREGION short, LON float, LAT float
    -> TM_WORLD_BORDERS-0.3 (writer GEOJSON_1)
TM_WORLD_BORDERS-0.3 (writer GEOJSON_1)
    attributes: FIPS string, ISO2 string, ISO3 string, UN int, NAME string, AREA int, POP2005 int, REGION int, SUBREGION int, LON float, LAT float
