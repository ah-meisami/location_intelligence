FME workspace esrishape2geojson_street_line.fmw

Parameters:
- SourceDataset_ESRISHAPE = C:\Users\Ah_Meisami\Downloads\Compressed\TEHRAN-SHP-FILES-Full-VIP_1756444_5162\TEHRAN\squar stree brigh\street-line.shp   # Source Esri Shapefile(s)
- DestDataset_GEOJSON = C:\Users\Ah_Meisami\Desktop\call wms from leaflet\street-line.json   # Destination GeoJSON File

Readers:
- ESRISHAPE_1: ESRISHAPE from $(SourceDataset_ESRISHAPE)

Writers:
- GEOJSON_1: GEOJSON to $(DestDataset_GEOJSON)

street-line (reader ESRISHAPE_1)
    attributes: ENTITY char(14), MSLINK_DMR number(16,0), MAPID short, NAME char(35), FNAME char(32)
    -> street-line (writer GEOJSON_1)
street-line (writer GEOJSON_1)
    attributes: ENTITY string, MSLINK_DMR int, MAPID int, NAME string, FNAME string
