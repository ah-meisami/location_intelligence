FME workspace xlsxr2geojson.13970217.7_12.fmw

Parameters:
- SourceDataset_XLSXR_9 = C:\Users\Ah_Meisami\Desktop\call wms from leaflet\data\excel\1-6.xlsx   # Source Microsoft Excel File(s)
- SourceDataset_XLSXR_14 = C:\Users\Ah_Meisami\Desktop\call wms from leaflet\data\excel\7-12.xlsx   # Source Microsoft Excel File(s)
- DestDataset_GEOJSON_12 = C:\Users\Ah_Meisami\Desktop\call wms from leaflet\data\geojson\tejarat.json   # Destination GeoJSON File
- SourceDataset_XLSXR = C:\Users\Ah_Meisami\Desktop\call wms from leaflet\data\excel\7-12.xlsx   # Source Microsoft Excel File(s)
- DestDataset_GEOJSON = C:\Users\Ah_Meisami\Desktop\call wms from leaflet\data\geojson\tose_tavon.json   # Destination GeoJSON File
- SourceDataset_XLSXR_12 = C:\Users\Ah_Meisami\Desktop\call wms from leaflet\data\excel\7-12.xlsx   # Source Microsoft Excel File(s)
- SourceDataset_XLSXR_10 = C:\Users\Ah_Meisami\Desktop\call wms from leaflet\data\excel\7-12.xlsx   # Source Microsoft Excel File(s)
- SourceDataset_XLSXR_7 = C:\Users\Ah_Meisami\Desktop\call wms from leaflet\data\excel\7-12.xlsx   # Source Microsoft Excel File(s)
- SourceDataset_XLSXR_11 = C:\Users\Ah_Meisami\Desktop\call wms from leaflet\data\excel\7-12.xlsx   # Source Microsoft Excel File(s)
- DestDataset_GEOJSON_10 = C:\Users\Ah_Meisami\Desktop\call wms from leaflet\data\geojson\day.json   # Destination GeoJSON File
- DestDataset_GEOJSON_8 = C:\Users\Ah_Meisami\Desktop\call wms from leaflet\data\geojson\middle_east.json   # Destination GeoJSON File
- DestDataset_GEOJSON_6 = C:\Users\Ah_Meisami\Desktop\call wms from leaflet\data\geojson\hekmat_iranaian.json   # Destination GeoJSON File
- DestDataset_GEOJSON_9 = C:\Users\Ah_Meisami\Desktop\call wms from leaflet\data\geojson\export_development.json   # Destination GeoJSON File

Readers:
- XLSXR_2: XLSXR from $(SourceDataset_XLSXR_9) in LL84
- XLSXR_8: XLSXR from $(SourceDataset_XLSXR_14) in LL84
- XLSXR_1: XLSXR from $(SourceDataset_XLSXR) in LL84
- XLSXR_3: XLSXR from $(SourceDataset_XLSXR_12) in LL84
- XLSXR_4: XLSXR from $(SourceDataset_XLSXR_10) in LL84
- XLSXR_5: XLSXR from $(SourceDataset_XLSXR_7) in LL84
- XLSXR_6: XLSXR from $(SourceDataset_XLSXR_11) in LL84

Writers:
- GEOJSON_7: GEOJSON to $(DestDataset_GEOJSON_12)
- GEOJSON_1: GEOJSON to $(DestDataset_GEOJSON)
- GEOJSON_2: GEOJSON to $(DestDataset_GEOJSON_10)
- GEOJSON_3: GEOJSON to $(DestDataset_GEOJSON_8)
- GEOJSON_4: GEOJSON to $(DestDataset_GEOJSON_6)
- GEOJSON_5: GEOJSON to $(DestDataset_GEOJSON_9)

export_development (reader XLSXR_3)
    attributes: branchId number(5,0), branchcode number(5,0), branchname char(13), address char(76), telephone number(9,0), fax number(9,0), zipcode z_coordinate, atm char(4), currencyService char(3), safeDeposit char(3), queueSystem char(4), issuanceCard char(3), parking char(3), eveningTime char(3), swift char(3), pinpad char(3), sms char(3), telebank char(3), webKiosk char(3), pls char(3), latitude y_coordinate, longitude x_coordinate, bankid number(5,0), cityId number(4,0), pos char(3), shetab char(4), workhours char(33), cityname char(9), provincename char(20), bankname char(24),
      logo char(27), provinceid number(3,0), telcode number(4,0), citytelcode number(3,0)
    -> export_development (writer GEOJSON_5)
export_development (writer GEOJSON_5)
    attributes: branchId int, branchcode int, branchname string, address string, telephone int, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode int
hekmat_iranaian (reader XLSXR_4)
    attributes: branchId number(5,0), branchcode number(5,0), branchname char(24), address char(101), telephone char(24), fax number(11,0), zipcode string, atm char(4), currencyService char(3), safeDeposit char(3), queueSystem char(4), issuanceCard char(4), parking char(3), eveningTime char(3), swift char(3), pinpad char(3), sms char(3), telebank char(3), webKiosk char(3), pls char(3), latitude y_coordinate, longitude x_coordinate, bankid number(5,0), cityId number(4,0), pos char(3), shetab char(4), workhours char(30), cityname char(17), provincename char(12), bankname char(19),
      logo char(24), provinceid number(3,0), telcode number(3,0), citytelcode string
    -> hekmat_iranaian (writer GEOJSON_4)
hekmat_iranaian (writer GEOJSON_4)
    attributes: branchId int, branchcode int, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
middle_east (reader XLSXR_5)
    attributes: branchId number(5,0), branchcode number(5,0), branchname char(15), address char(70), telephone char(26), fax char(13), zipcode z_coordinate, atm char(4), currencyService char(4), safeDeposit char(4), queueSystem char(4), issuanceCard char(3), parking char(4), eveningTime char(3), swift char(3), pinpad char(3), sms char(3), telebank char(3), webKiosk char(3), pls char(3), latitude y_coordinate, longitude x_coordinate, bankid number(5,0), cityId number(4,0), pos char(3), shetab char(4), workhours char(30), cityname char(7), provincename char(15), bankname char(15),
      logo char(20), provinceid number(3,0), telcode number(3,0), citytelcode string
    -> middle_east (writer GEOJSON_3)
middle_east (writer GEOJSON_3)
    attributes: branchId int, branchcode int, branchname string, address string, telephone string, fax string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
day (reader XLSXR_6)
    attributes: branchId number(5,0), branchcode number(5,0), branchname char(18), address char(95), telephone char(27), fax number(9,0), zipcode z_coordinate, atm char(4), currencyService char(3), safeDeposit char(3), queueSystem char(4), issuanceCard char(4), parking char(3), eveningTime char(3), swift char(3), pinpad char(3), sms char(4), telebank char(4), webKiosk char(4), pls char(3), latitude y_coordinate, longitude x_coordinate, bankid number(5,0), cityId number(4,0), pos char(3), shetab char(4), workhours char(30), cityname char(7), provincename char(12), bankname char(8),
      logo char(12), provinceid number(3,0), telcode number(3,0), citytelcode string
    -> day (writer GEOJSON_2)
day (writer GEOJSON_2)
    attributes: branchId int, branchcode int, branchname string, address string, telephone string, fax int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
tejarat (reader XLSXR_8)
    attributes: branchId number(5,0), branchcode char(12), branchname char(38), address char(101), telephone char(21), fax number(11,0), zipcode char(12), atm char(4), currencyService char(4), safeDeposit char(4), queueSystem char(4), issuanceCard char(4), parking char(4), eveningTime char(4), swift char(4), pinpad char(4), sms char(4), telebank char(4), webKiosk char(3), pls char(4), latitude y_coordinate, longitude x_coordinate, bankid number(5,0), cityId number(4,0), pos char(4), shetab char(4), workhours char(31), cityname char(17), provincename char(12), bankname char(11),
      logo char(16), provinceid number(3,0), telcode number(3,0), citytelcode string
    -> tejarat (writer GEOJSON_7)
tejarat (writer GEOJSON_7)
    attributes: branchId int, branchcode string, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
tose_tavon (reader XLSXR_1)
    attributes: branchId number(5,0), branchcode number(5,0), branchname char(32), address char(86), telephone number(9,0), fax number(11,0), zipcode string, atm char(4), currencyService char(3), safeDeposit char(3), queueSystem char(4), issuanceCard char(3), parking char(3), eveningTime char(3), swift char(3), pinpad char(3), sms char(3), telebank char(3), webKiosk char(3), pls char(3), latitude y_coordinate, longitude x_coordinate, bankid number(5,0), cityId number(3,0), pos char(3), shetab char(4), workhours char(30), cityname char(10), provincename char(6), bankname char(17),
      logo char(19), provinceid number(2,0), telcode number(3,0), citytelcode string
    -> tose_tavon (writer GEOJSON_1)
tose_tavon (writer GEOJSON_1)
    attributes: branchId int, branchcode int, branchname string, address string, telephone int, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
