FME workspace esrishape2geojson_IRN_adm0.fmw

Parameters:
- SourceDataset_ESRISHAPE = C:\Users\Ah_Meisami\Downloads\Compressed\IRN_adm\IRN_adm0.shp   # Source Esri Shapefile(s)
- DestDataset_GEOJSON = C:\Users\Ah_Meisami\Desktop\call wms from leaflet\IRN_adm0.json   # Destination GeoJSON File

Readers:
- ESRISHAPE_1: ESRISHAPE from $(SourceDataset_ESRISHAPE)

Writers:
- GEOJSON_1: GEOJSON to $(DestDataset_GEOJSON)

IRN_adm0 (reader ESRISHAPE_1)
    attributes: ID_0 long, ISO char(3), NAME_0 char(75), OBJECTID_1 long, ISO3 char(5), NAME_ENGLI char(50), NAME_ISO char(54), NAME_FAO char(50), NAME_LOCAL char(54), NAME_OBSOL char(150), NAME_VARIA char(160), NAME_NONLA char(50), NAME_FRENC char(50), NAME_SPANI char(50), NAME_RUSSI char(50), NAME_ARABI char(50), NAME_CHINE char(50), WASPARTOF char(100), CONTAINS char(50), SOVEREIGN char(40), ISO2 char(4), WWW char(2), FIPS char(6), ISON double, VALIDFR char(12), VALIDTO char(10), POP2000 double, SQKM double, POPSQKM double, UNREGION1 char(254),
      UNREGION2 char(254), DEVELOPING double, CIS double, Transition double, OECD double, WBREGION char(254), WBINCOME char(254), WBDEBT char(254), WBOTHER char(254), CEEAC double, CEMAC double, CEPLG double, COMESA double, EAC double, ECOWAS double, IGAD double, IOC double, MRU double, SACU double, UEMOA double, UMA double, PALOP double, PARTA double, CACM double, EurAsEC double, Agadir double, SAARC double, ASEAN double, NAFTA double, GCC double,
      CSN double, CARICOM double, EU double, CAN double, ACP double, Landlocked double, AOSIS double, SIDS double, Islands double, LDC double
    -> IRN_adm0 (writer GEOJSON_1)
IRN_adm0 (writer GEOJSON_1)
    attributes: ID_0 int, ISO string, NAME_0 string, OBJECTID_1 int, ISO3 string, NAME_ENGLI string, NAME_ISO string, NAME_FAO string, NAME_LOCAL string, NAME_OBSOL string, NAME_VARIA string, NAME_NONLA string, NAME_FRENC string, NAME_SPANI string, NAME_RUSSI string, NAME_ARABI string, NAME_CHINE string, WASPARTOF string, CONTAINS string, SOVEREIGN string, ISO2 string, WWW string, FIPS string, ISON float, VALIDFR string, VALIDTO string, POP2000 float, SQKM float, POPSQKM float, UNREGION1 string,
      UNREGION2 string, DEVELOPING float, CIS float, Transition float, OECD float, WBREGION string, WBINCOME string, WBDEBT string, WBOTHER string, CEEAC float, CEMAC float, CEPLG float, COMESA float, EAC float, ECOWAS float, IGAD float, IOC float, MRU float, SACU float, UEMOA float, UMA float, PALOP float, PARTA float, CACM float, EurAsEC float, Agadir float, SAARC float, ASEAN float, NAFTA float, GCC float,
      CSN float, CARICOM float, EU float, CAN float, ACP float, Landlocked float, AOSIS float, SIDS float, Islands float, LDC float
