FME workspace esrishape2geojson_power_line.fmw

Parameters:
- SourceDataset_ESRISHAPE = C:\Users\Ah_Meisami\Downloads\Compressed\TEHRAN-SHP-FILES-Full-VIP_1756444_5162\TEHRAN\hesar\power-line-line.shp   # Source Esri Shapefile(s)
- DestDataset_GEOJSON = C:\Users\Ah_Meisami\Desktop\call wms from leaflet\power_line.json   # Destination GeoJSON File

Readers:
- ESRISHAPE_1: ESRISHAPE from $(SourceDataset_ESRISHAPE)

Writers:
- GEOJSON_1: GEOJSON to $(DestDataset_GEOJSON)

power-line-line (reader ESRISHAPE_1)
    attributes: ENTITY char(14), MSLINK_DMR number(11,0), FNAME char(32), MAPID short, VOLTAGE long, BOUND long, OPERATION_ char(17)
    -> power-line-line (writer GEOJSON_1)
power-line-line (writer GEOJSON_1)
    attributes: ENTITY string, MSLINK_DMR int, FNAME string, MAPID int, VOLTAGE int, BOUND int, OPERATION_ string
