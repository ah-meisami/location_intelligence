FME workspace xlsxr2geojson.13970217.1_6.fmw

Parameters:
- SourceDataset_XLSXR = C:\Users\Ah_Meisami\Desktop\call wms from leaflet\data\excel\1-6.xlsx   # Source Microsoft Excel File(s)
- DestDataset_GEOJSON = C:\Users\Ah_Meisami\Desktop\call wms from leaflet\data\geojson\eghtesad_novin.json   # Destination GeoJSON File
- SourceDataset_XLSXR_9 = C:\Users\Ah_Meisami\Desktop\call wms from leaflet\data\excel\1-6.xlsx   # Source Microsoft Excel File(s)
- SourceDataset_XLSXR_13 = C:\Users\Ah_Meisami\Desktop\call wms from leaflet\data\excel\1-6.xlsx   # Source Microsoft Excel File(s)
- DestDataset_GEOJSON_9 = C:\Users\Ah_Meisami\Desktop\call wms from leaflet\data\geojson\ansar.json   # Destination GeoJSON File
- SourceDataset_XLSXR_11 = C:\Users\Ah_Meisami\Desktop\call wms from leaflet\data\excel\1-6.xlsx   # Source Microsoft Excel File(s)
- DestDataset_GEOJSON_13 = C:\Users\Ah_Meisami\Desktop\call wms from leaflet\data\geojson\iran_zamin.json   # Destination GeoJSON File
- SourceDataset_XLSXR_15 = C:\Users\Ah_Meisami\Desktop\call wms from leaflet\data\excel\1-6.xlsx   # Source Microsoft Excel File(s)
- DestDataset_GEOJSON_11 = C:\Users\Ah_Meisami\Desktop\call wms from leaflet\data\geojson\ayande.json   # Destination GeoJSON File
- SourceDataset_XLSXR_10 = C:\Users\Ah_Meisami\Desktop\call wms from leaflet\data\excel\1-6.xlsx   # Source Microsoft Excel File(s)
- DestDataset_GEOJSON_8 = C:\Users\Ah_Meisami\Desktop\call wms from leaflet\data\geojson\parsian.json   # Destination GeoJSON File
- SourceDataset_XLSXR_12 = C:\Users\Ah_Meisami\Desktop\call wms from leaflet\data\excel\1-6.xlsx   # Source Microsoft Excel File(s)
- DestDataset_GEOJSON_10 = C:\Users\Ah_Meisami\Desktop\call wms from leaflet\data\geojson\passargad.json   # Destination GeoJSON File
- SourceDataset_XLSXR_14 = C:\Users\Ah_Meisami\Desktop\call wms from leaflet\data\excel\7-12.xlsx   # Source Microsoft Excel File(s)
- DestDataset_GEOJSON_12 = C:\Users\Ah_Meisami\Desktop\call wms from leaflet\data\geojson\tejarat.json   # Destination GeoJSON File

Readers:
- XLSXR_1: XLSXR from $(SourceDataset_XLSXR) in LL84
- XLSXR_2: XLSXR from $(SourceDataset_XLSXR_9) in LL84
- XLSXR_3: XLSXR from $(SourceDataset_XLSXR_13) in LL84
- XLSXR_4: XLSXR from $(SourceDataset_XLSXR_11) in LL84
- XLSXR_5: XLSXR from $(SourceDataset_XLSXR_15) in LL84
- XLSXR_6: XLSXR from $(SourceDataset_XLSXR_10) in LL84
- XLSXR_7: XLSXR from $(SourceDataset_XLSXR_12) in LL84
- XLSXR_8: XLSXR from $(SourceDataset_XLSXR_14) in LL84

Writers:
- GEOJSON_1: GEOJSON to $(DestDataset_GEOJSON)
- GEOJSON_2: GEOJSON to $(DestDataset_GEOJSON_9)
- GEOJSON_3: GEOJSON to $(DestDataset_GEOJSON_13)
- GEOJSON_4: GEOJSON to $(DestDataset_GEOJSON_11)
- GEOJSON_5: GEOJSON to $(DestDataset_GEOJSON_8)
- GEOJSON_6: GEOJSON to $(DestDataset_GEOJSON_10)
- GEOJSON_7: GEOJSON to $(DestDataset_GEOJSON_12)

eghtesad_novin (reader XLSXR_1)
    attributes: branchId number(5,0), branchcode number(5,0), branchname char(34), address char(255), telephone char(49), fax char(10), zipcode string, atm char(4), currencyService char(3), safeDeposit char(3), queueSystem char(4), issuanceCard char(3), parking char(3), eveningTime char(3), swift char(3), pinpad char(3), sms char(3), telebank char(3), webKiosk char(3), pls char(3), latitude y_coordinate, longitude x_coordinate, bankid number(2,0), cityId number(4,0), pos char(3), shetab char(4), workhours char(31), cityname char(17), provincename char(9), bankname char(17),
      logo char(23), provinceid number(3,0), telcode number(3,0), citytelcode string
    -> eghtesad_novin (writer GEOJSON_1)
eghtesad_novin (writer GEOJSON_1)
    attributes: branchId int, branchcode int, branchname string, address string, telephone string, fax string, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
ansar (reader XLSXR_3)
    attributes: branchId number(5,0), branchcode number(5,0), branchname char(24), address char(100), telephone char(37), F char(21), zipcode z_coordinate, atm char(4), currencyService char(4), safeDeposit char(3), queueSystem char(4), issuanceCard char(4), parking char(3), eveningTime char(3), swift char(3), pinpad char(3), sms char(3), telebank char(3), webKiosk char(3), pls char(3), latitude y_coordinate, longitude x_coordinate, bankid number(5,0), cityId number(4,0), pos char(4), shetab char(4), workhours char(30), cityname char(13), provincename char(12), bankname char(11),
      logo char(14), provinceid number(3,0), telcode number(3,0), citytelcode string
    -> ansar (writer GEOJSON_2)
ansar (writer GEOJSON_2)
    attributes: branchId int, branchcode int, branchname string, address string, telephone string, F string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
iran_zamin (reader XLSXR_4)
    attributes: branchId number(5,0), branchcode number(5,0), branchname char(19), address char(91), telephone number(9,0), F number(9,0), zipcode z_coordinate, atm char(4), currencyService char(4), safeDeposit char(3), queueSystem char(4), issuanceCard char(3), parking char(3), eveningTime char(3), swift char(3), pinpad char(4), sms char(3), telebank char(3), webKiosk char(3), pls char(3), latitude y_coordinate, longitude x_coordinate, bankid number(5,0), cityId number(4,0), pos char(4), shetab char(4), workhours char(30), cityname char(15), provincename char(12), bankname char(16),
      logo char(19), provinceid number(3,0), telcode number(3,0), citytelcode string
    -> iran_zamin (writer GEOJSON_3)
iran_zamin (writer GEOJSON_3)
    attributes: branchId int, branchcode int, branchname string, address string, telephone int, F int, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
ayande (reader XLSXR_5)
    attributes: branchId number(5,0), branchcode number(5,0), branchname char(40), address char(101), telephone char(26), fax char(13), zipcode z_coordinate, atm char(4), currencyService char(4), safeDeposit char(4), queueSystem char(4), issuanceCard char(4), parking char(4), eveningTime char(4), swift char(4), pinpad char(4), sms char(4), telebank char(4), webKiosk char(4), pls char(4), latitude y_coordinate, longitude x_coordinate, bankid number(5,0), cityId number(4,0), pos char(3), shetab char(4), workhours char(48), cityname char(12), provincename char(12), bankname char(11),
      logo char(15), provinceid number(3,0), telcode number(3,0), citytelcode string
    -> ayande (writer GEOJSON_4)
ayande (writer GEOJSON_4)
    attributes: branchId int, branchcode int, branchname string, address string, telephone string, fax string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
parsian (reader XLSXR_6)
    attributes: branchId number(5,0), branchcode number(5,0), branchname char(30), address char(98), telephone char(41), F char(13), zipcode z_coordinate, atm char(4), currencyService char(4), safeDeposit char(4), queueSystem char(4), issuanceCard char(4), parking char(3), eveningTime char(3), swift char(3), pinpad char(3), sms char(4), telebank char(4), webKiosk char(3), pls char(3), latitude y_coordinate, longitude x_coordinate, bankid number(2,0), cityId number(4,0), pos char(3), shetab char(4), workhours char(30), cityname char(10), provincename char(15), bankname char(13),
      logo char(16), provinceid number(3,0), telcode number(3,0), citytelcode string
    -> parsian (writer GEOJSON_5)
parsian (writer GEOJSON_5)
    attributes: branchId int, branchcode int, branchname string, address string, telephone string, F string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
passargad (reader XLSXR_7)
    attributes: branchId number(5,0), branchcode number(5,0), branchname char(24), address char(100), telephone char(20), F char(17), zipcode z_coordinate, atm char(4), currencyService char(4), safeDeposit char(3), queueSystem char(4), issuanceCard char(4), parking char(3), eveningTime char(3), swift char(3), pinpad char(3), sms char(4), telebank char(4), webKiosk char(3), pls char(4), latitude y_coordinate, longitude x_coordinate, bankid number(2,0), cityId number(4,0), pos char(3), shetab char(4), workhours char(31), cityname char(17), provincename char(12), bankname char(14),
      logo char(18), provinceid number(3,0), telcode number(3,0), citytelcode string
    -> passargad (writer GEOJSON_6)
passargad (writer GEOJSON_6)
    attributes: branchId int, branchcode int, branchname string, address string, telephone string, F string, zipcode float, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
tejarat (reader XLSXR_8)
    attributes: branchId number(5,0), branchcode char(12), branchname char(38), address char(101), telephone char(21), fax number(11,0), zipcode char(12), atm char(4), currencyService char(4), safeDeposit char(4), queueSystem char(4), issuanceCard char(4), parking char(4), eveningTime char(4), swift char(4), pinpad char(4), sms char(4), telebank char(4), webKiosk char(3), pls char(4), latitude y_coordinate, longitude x_coordinate, bankid number(5,0), cityId number(4,0), pos char(4), shetab char(4), workhours char(31), cityname char(17), provincename char(12), bankname char(11),
      logo char(16), provinceid number(3,0), telcode number(3,0), citytelcode string
    -> tejarat (writer GEOJSON_7)
tejarat (writer GEOJSON_7)
    attributes: branchId int, branchcode string, branchname string, address string, telephone string, fax int, zipcode string, atm string, currencyService string, safeDeposit string, queueSystem string, issuanceCard string, parking string, eveningTime string, swift string, pinpad string, sms string, telebank string, webKiosk string, pls string, latitude float, longitude float, bankid int, cityId int, pos string, shetab string, workhours string, cityname string, provincename string, bankname string,
      logo string, provinceid int, telcode int, citytelcode string
