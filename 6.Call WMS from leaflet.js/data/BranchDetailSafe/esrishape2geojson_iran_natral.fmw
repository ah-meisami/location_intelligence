FME workspace esrishape2geojson_iran_natral.fmw

Parameters:
- SourceDataset_ESRISHAPE = C:\Users\Ah_Meisami\Downloads\Compressed\iran-natural-features\iran_natural.shp   # Source Esri Shapefile(s)
- DestDataset_GEOJSON = C:\Users\Ah_Meisami\Downloads\Compressed\iran-natural-features\iran_natural.json   # Destination GeoJSON File

Readers:
- ESRISHAPE_1: ESRISHAPE from $(SourceDataset_ESRISHAPE)

Writers:
- GEOJSON_1: GEOJSON to $(DestDataset_GEOJSON)

iran_natural (reader ESRISHAPE_1)
    attributes: osm_id number(11,0), name char(48), type char(16)
    -> iran_natural (writer GEOJSON_1)
iran_natural (writer GEOJSON_1)
    attributes: osm_id int, name string, type string
